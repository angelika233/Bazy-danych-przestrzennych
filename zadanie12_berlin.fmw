FME workspace zadanie12_berlin.fmw

Parameters:
- SourceDataset_SHAPEFILE = $(FME_MF_DIR)T2019_KAR_STREETS.shp   # Source Esri Shapefile(s)
- SourceDataset_SHAPEFILE_5 = $(FME_MF_DIR)T2019_KAR_STREET_NODE.shp   # Source Esri Shapefile(s)
- SourceDataset_SHAPEFILE_4 = $(FME_MF_DIR)T2019_KAR_POI_TABLE.shp   # Source Esri Shapefile(s)
- SourceDataset_CSV2 = $(FME_MF_DIR)punkty.txt   # Source CSV (Comma Separated Value) File(s)
- SourceDataset_CSV2_5 = $(FME_MF_DIR)punkty.txt   # Source CSV (Comma Separated Value) File(s)
- SourceDataset_CSV2_4 = $(FME_MF_DIR)punkty.txt   # Source CSV (Comma Separated Value) File(s)
- DestDataset_GEOJSON = $(FME_MF_DIR)punkty_buffor.json   # Destination GeoJSON File
- DestDataset_GEOJSON_3 = $(FME_MF_DIR)punkty_buffor.json   # Destination GeoJSON File
- DestDataset_GEODATABASE_FILE = $(FME_MF_DIR)node.gdb   # File Geodatabase
- DestDataset_GEODATABASE_FILE_5 = $(FME_MF_DIR)node.gdb   # File Geodatabase
- DestDataset_XML = $(FME_MF_DIR)node.gdb\punkty.xml   # Destination XML (Extensible Markup Language) File
- DestDataset_XML_3 = $(FME_MF_DIR)node.gdb\punkty.xml   # Destination XML (Extensible Markup Language) File
- DestDataset_GEODATABASE_FILE_4 = $(FME_MF_DIR)node.gdb   # File Geodatabase

Readers:
- SHAPEFILE_1: SHAPEFILE from $(SourceDataset_SHAPEFILE) in LL-WGS84
- SHAPEFILE_2: SHAPEFILE from $(SourceDataset_SHAPEFILE_5) in LL-WGS84
- SHAPEFILE_3: SHAPEFILE from $(SourceDataset_SHAPEFILE_4) in LL-WGS84
- CSV2_1: CSV2 from $(SourceDataset_CSV2) in LL-WGS84
- CSV2_2: CSV2 from $(SourceDataset_CSV2_5) in LL-WGS84
- CSV2_3: CSV2 from $(SourceDataset_CSV2_4) in LL-WGS84

Writers:
- GEOJSON_1: GEOJSON to $(DestDataset_GEOJSON)
- GEOJSON_2: GEOJSON to $(DestDataset_GEOJSON_3)
- GEODATABASE_FILE_1: GEODATABASE_FILE to $(DestDataset_GEODATABASE_FILE)
- GEODATABASE_FILE_2: GEODATABASE_FILE to $(DestDataset_GEODATABASE_FILE_5)
- XML_1: XML to $(DestDataset_XML)
- XML_2: XML to $(DestDataset_XML_3)
- GEODATABASE_FILE_3: GEODATABASE_FILE to $(DestDataset_GEODATABASE_FILE_4)

CSV (reader CSV2_3)
    attributes: x x_coordinate, y y_coordinate
    -> LineBuilder
LineBuilder
    ACCUM_INPUT_ATTRS = Use Attributes From One Feature
    GROUP_BY = fme_feature_type
    REMOVE_DUPLICATES = No
    LINE -> Reprojector_4
Reprojector_4
    DEST = DHDN.Berlin/Cassini
    INTERPOLATION_TYPE_NAME = Nearest Neighbor
    RASTER_CELL_SIZE = Preserve Cells
    RASTER_TOLERANCE = 0.0
    SOURCE = Read from feature
    REPROJECTED -> ShortestPathFinder [FROM-TO]
    REPROJECTED -> ShortestPathFinder_2 [FROM-TO]
T2019_KAR_STREETS (reader SHAPEFILE_1)
    attributes: LINK_ID long, ST_NAME char(254), REF_IN_ID long, NREF_IN_ID long, FUNC_CLASS char(1), SPEED_CAT char(1), FR_SPEED_L long, TO_SPEED_L long, DIR_TRAVEL char(1)
    -> Reprojector
Reprojector
    DEST = DHDN.Berlin/Cassini
    INTERPOLATION_TYPE_NAME = Nearest Neighbor
    RASTER_CELL_SIZE = Preserve Cells
    RASTER_TOLERANCE = 0.0
    SOURCE = Read from feature
    REPROJECTED -> ShortestPathFinder [NETWORK]
    REPROJECTED -> Tester
ShortestPathFinder
    ALLOW_UTURNS = Yes
    REORDER_CHOICE = None
    REORDER_CONDITIONS = ANY
    REORDER_ITERATIONS = 10000
    REORDER_VERIFICATIONS = 1
    SNAP_POINTS = No
    WEIGHT_ATTR_CHOICE = By Length
    PATH -> Bufferer
    PATH -> PointOnLineOverlayer_2 [LINE]
    PATH -> LengthCalculator_2
Bufferer
    ANGLE = 22.5
    CAP_STYLE = Arc
    CORNER_STYLE = Arc
    MODE = AREA
    OFFSET = 5
    OFFSET_UNITS = METERS
    PRECISION = APPROX
    BUFFERED -> PointOnAreaOverlayer [AREA]
LengthCalculator_2
    DIM = 2
    LEN_ATTR = _length
    MULT = 1
    -> AttributeManager_4
Tester
    BOOL_OP = OR
    COMPOSITE_TEST = 1
    TEST_CLAUSE = TEST @Value(DIR_TRAVEL) = F
    TEST_MODE = TEST
    PASSED -> AttributeManager
    FAILED -> Tester_6
AttributeManager
    ATTR_TABLE:
      SET_TO forward_cost = 1
      SET_TO reverse_cost = 9999
    -> ShortestPathFinder_2 [NETWORK]
Tester_6
    BOOL_OP = OR
    COMPOSITE_TEST = 1
    TEST_CLAUSE = TEST @Value(DIR_TRAVEL) = B
    TEST_MODE = TEST
    PASSED -> AttributeManager_2
    FAILED -> AttributeManager_5
AttributeManager_2
    ATTR_TABLE:
      SET_TO forward_cost = 1
      SET_TO reverse_cost = 1
    -> ShortestPathFinder_2 [NETWORK]
AttributeManager_5
    ATTR_TABLE:
      SET_TO forward_cost = 9999
      SET_TO reverse_cost = 1
    -> ShortestPathFinder_2 [NETWORK]
ShortestPathFinder_2
    ALLOW_UTURNS = Yes
    REORDER_CHOICE = None
    SNAP_POINTS = No
    WEIGHT_ATTR_1 = forward_cost
    WEIGHT_ATTR_2 = reverse_cost
    WEIGHT_ATTR_CHOICE = By Two Attributes
    PATH -> Bufferer_2
    PATH -> PointOnLineOverlayer [LINE]
    PATH -> LengthCalculator
Bufferer_2
    ANGLE = 22.5
    CAP_STYLE = Arc
    CORNER_STYLE = Arc
    MODE = AREA
    OFFSET = 5
    OFFSET_UNITS = METERS
    PRECISION = APPROX
    BUFFERED -> PointOnAreaOverlayer_2 [AREA]
LengthCalculator
    DIM = 2
    LEN_ATTR = _length
    MULT = 1
    -> AttributeManager_3
T2019_KAR_STREET_NODE (reader SHAPEFILE_2)
    attributes: NODE_ID long, LINK_ID long, POINT_NUM long, Z_LEVEL long, INTERSECT char(1), LAT double, LON double
    -> Reprojector_2
Reprojector_2
    DEST = DHDN.Berlin/Cassini
    INTERPOLATION_TYPE_NAME = Nearest Neighbor
    RASTER_CELL_SIZE = Preserve Cells
    RASTER_TOLERANCE = 0.0
    SOURCE = Read from feature
    REPROJECTED -> PointOnLineOverlayer [POINT]
    REPROJECTED -> PointOnLineOverlayer_2 [POINT]
PointOnLineOverlayer
    DEAGGREGATE_INPUT = Yes
    MEASURE_TYPE = Continuous
    MERGE_MEASURES = Yes
    OV_ATTR = _overlaps
    TOLERANCE = 1
    POINT -> Tester_4
Tester_4
    BOOL_OP = OR
    COMPOSITE_TEST = 1
    TEST_CLAUSE = TEST @Value(_overlaps) = 1
    TEST_MODE = TEST
    PASSED -> StatisticsCalculator
StatisticsCalculator
    CALCULATION_MODE = NUMERIC
    FEAT_STATS = LAT,NUMERIC_MODE,MIN,MAX,,,,,,,,,,;LON,NUMERIC_MODE,MIN,MAX,,,,,,,,,,;LINK_ID,NUMERIC_MODE,,,COUNT,,,,,,,,,;NODE_ID,NUMERIC_MODE,,,COUNT,,,,,,,,,
    SUMMARY -> Inspector_3
    SUMMARY -> AttributeManager_3
Inspector_3
AttributeManager_3
    ATTR_TABLE:
      SET_TO _length = @Value(_length)
      REMOVE x
      REMOVE y
      REMOVE _total_cost
    -> Aggregator
Aggregator
    ACCUM_ATTRS_NAME = Drop Incoming Attributes
    AGGREGATE_TYPE = Homogeneous Collection (If Possible)
    CONCAT_ATTRS = LAT.max LAT.min LINK_ID.total_count LON.max LON.min NODE_ID.total_count _length
    MODE = Geometry - Assemble One Level
    AGGREGATE -> Inspector_2
    AGGREGATE -> FeatureClass1 (writer GEODATABASE_FILE_3)
Inspector_2
PointOnLineOverlayer_2
    DEAGGREGATE_INPUT = Yes
    MEASURE_TYPE = Continuous
    MERGE_MEASURES = Yes
    OV_ATTR = _overlaps
    TOLERANCE = 1
    POINT -> Tester_5
Tester_5
    BOOL_OP = OR
    COMPOSITE_TEST = 1
    TEST_CLAUSE = TEST @Value(_overlaps) = 1
    TEST_MODE = TEST
    PASSED -> StatisticsCalculator_2
StatisticsCalculator_2
    CALCULATION_MODE = NUMERIC
    FEAT_STATS = LAT,NUMERIC_MODE,MIN,MAX,,,,,,,,,,;LON,NUMERIC_MODE,MIN,MAX,,,,,,,,,,;LINK_ID,NUMERIC_MODE,,,COUNT,,,,,,,,,;NODE_ID,NUMERIC_MODE,,,COUNT,,,,,,,,,
    SUMMARY -> AttributeManager_4
AttributeManager_4
    ATTR_TABLE:
      SET_TO _length = @Value(_length)
      REMOVE x
      REMOVE y
      REMOVE _total_cost
    -> Aggregator_2
Aggregator_2
    ACCUM_ATTRS_NAME = Drop Incoming Attributes
    AGGREGATE_TYPE = Homogeneous Collection (If Possible)
    CONCAT_ATTRS = LAT.max LAT.min LINK_ID.total_count LON.max LON.min NODE_ID.total_count _length
    MODE = Geometry - Assemble One Level
    AGGREGATE -> Inspector_4
    AGGREGATE -> FeatureClass1 (writer GEODATABASE_FILE_3)
FeatureClass1 (writer GEODATABASE_FILE_3)
    attributes: LAT_min double, LAT_max double, LON_min double, LON_max double, LINK_ID_total_count char(20), NODE_ID_total_count char(20), _length double
Inspector_4
T2019_KAR_POI_TABLE (reader SHAPEFILE_3)
    attributes: POI_ID long, LINK_ID long, TYPE char(250), POI_NAME char(250), ST_NAME char(250), LAT double, LON double
    -> Reprojector_3
Reprojector_3
    DEST = DHDN.Berlin/Cassini
    INTERPOLATION_TYPE_NAME = Nearest Neighbor
    RASTER_CELL_SIZE = Preserve Cells
    RASTER_TOLERANCE = 0.0
    SOURCE = Read from feature
    REPROJECTED -> PointOnAreaOverlayer [POINT]
    REPROJECTED -> PointOnAreaOverlayer_2 [POINT]
PointOnAreaOverlayer
    ATTR_ACCUM_MODE = Merge Incoming
    ATTR_CONFLICT_RES = Use Original
    CANDIDATE_LIST_ATTRS_TO_INCLUDE_MODE = Selected Attributes
    DEAGGREGATE_INPUT = Yes
    OV_ATTR = _overlaps
    POLYS_FIRST = No
    POINT -> Tester_2
Tester_2
    BOOL_OP = OR
    COMPOSITE_TEST = 1
    TEST_CLAUSE = TEST @Value(_overlaps) = 1
    TEST_MODE = TEST
    PASSED -> CSV (writer GEOJSON_2)
PointOnAreaOverlayer_2
    ATTR_ACCUM_MODE = Merge Incoming
    ATTR_CONFLICT_RES = Use Original
    CANDIDATE_LIST_ATTRS_TO_INCLUDE_MODE = Selected Attributes
    DEAGGREGATE_INPUT = Yes
    OV_ATTR = _overlaps
    POLYS_FIRST = No
    POINT -> Tester_3
Tester_3
    BOOL_OP = OR
    COMPOSITE_TEST = 1
    TEST_CLAUSE = TEST @Value(_overlaps) = 1
    TEST_MODE = TEST
    PASSED -> CSV (writer GEOJSON_2)
CSV (writer GEOJSON_2)
    attributes: POI_ID int, LINK_ID int, TYPE string, POI_NAME string, ST_NAME string, LAT float, LON float, _overlaps string
